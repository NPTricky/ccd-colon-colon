# J3Chess Requirements

# Specification: Specification Document
- Description: Requirements Document

## RQ-01 (Test Class)
Display the chessboard and all the pieces on their current fields.
- Method: (multiple)

### RQ-01-01 (Test Class)
Create a logical representation of the chessboard.
- Method: Chessboard.Chessboard

### RQ-01-02 (Test Class)
Create a logical representation of the pieces.
- Method: PieceFactory.create

### RQ-01-03 (Test Class)
Initialize a window and a panel to draw on.
- Method: DrawPanel.DrawPanel

### RQ-01-04 (Test Class)
Draw the chessboard itself.
- Method: PaintSystem.process

### RQ-01-05 (Test Class)
Draw the pieces onto the chessboard.
- Method: PaintSystem.process

## RQ-02 (Test Class)
Make a piece the current selection by clicking on it while its the piece's player's turn.
- Method: (multiple)

### RQ-02-01 (Test Class)
Capture the player's click and translate to field on chessboard.
- Method: DrawPanel.mouseButtonPressed

### RQ-02-02 (Test Class)
React to the player's click, depending on where he clicked.
- Method: HumanPlayerControler.notifyFieldPressed

### RQ-02-03 (Test Class)
Select the clicked entity if it belongs to the current player.
- Method: Game.selectPiece

### RQ-02-04 (Test Class)
Draw an overlay onto the selected piece.
- Class: SelectedSystem.process

## RQ-03 (Test Class)
Display the currently selected piece's possible moves.
- Method: (multiple)

### RQ-03-01 (Test Class)
Define the logic for each piece.
- Method: MotionPattern.MotionPattern

### RQ-03-02 (Test Class)
Calculate the possibly moves.
- Method: ValidMovement.getValidMoves

### RQ-03-03 (Test Class)
Draw the calculated moves onto the chessboard.
- Method: SelectedSystem.process

## RQ-04 (Test Class)
Move the currently selected piece to a new field on click if the move is legal.
- Method: (multiple)

### RQ-04-01 (Test Class)
Execute the move and switch to the next player.
- Method: Game.doMove

### RQ-04-02 (Test Class)
Add the move to the log table.
- Method: J3ChessView.addMove

## RQ-05 (Test Class)
Capture other figures according to the rules of 3 person chess.
- Method: (multiple)

### RQ-05-01 (Test Class)
Deactivate and hide the captured figure.
- Method: Move.execute

## RQ-06 (Test Class)
Make a player lose when his / her king is captured.
- Method: (multiple)

### RQ-06-01 (Test Class)
Deactivate the player.

### RQ-06-02 (Test Class)
When only one player remains, display a winning message.

## R7 (Test Class)

## R8

## R22 (Test Class)
